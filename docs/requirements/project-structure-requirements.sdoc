[REQUIREMENT]
UID: REQ-PROJ-001
TITLE: Project Folder Organization
STATEMENT: The ESPHome project shall organize device configurations by functional category rather than scattered at root level.
RATIONALE: Functional organization improves maintainability and navigation of device configurations.

[REQUIREMENT]
UID: REQ-PROJ-002
TITLE: Device Directory Structure
STATEMENT: Device configurations shall be organized in the following structure:
- devices/plugs/ - Smart plug configurations
- devices/lights/ - Smart light and bulb configurations  
- devices/safety/ - Safety equipment configurations
- devices/other/ - Miscellaneous device configurations
RATIONALE: Clear categorization by device function enables easier maintenance and discovery.

[REQUIREMENT]
UID: REQ-PROJ-003
TITLE: FCCID Preservation
STATEMENT: All device configurations shall maintain their FCCID associations through the fccid/ directory structure.
RATIONALE: FCCID compliance is required for device certification and regulatory compliance.

[REQUIREMENT]
UID: REQ-PROJ-004
TITLE: Configuration File Naming
STATEMENT: Device configuration files shall use descriptive names that indicate their purpose (e.g., tv_plug.yaml, hotwater_plug.yaml).
RATIONALE: Descriptive naming improves code readability and device identification.

[REQUIREMENT]
UID: REQ-PROJ-005
TITLE: Base Configuration Content Restrictions
STATEMENT: The config/base.yaml file shall only contain configurations that apply universally to all devices. Device-specific configurations including time servers, timezones, automation rules, and device-specific sensors shall not be included in base.yaml.
RATIONALE: Since base.yaml is included in all device configurations through FCCID templates, device-specific configurations would be incorrectly applied to all devices, causing conflicts and improper behavior.

[REQUIREMENT]
UID: REQ-PROJ-006
TITLE: Universal Base Configuration Content
STATEMENT: The config/base.yaml file shall only contain configurations that are truly universal across all devices, such as API settings, OTA platform settings, web server settings, and generic WiFi signal sensors using substitution variables.
RATIONALE: Universal configurations ensure consistent behavior across all devices while preventing device-specific settings from being incorrectly applied to all devices.
